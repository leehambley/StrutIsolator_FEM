# -*- coding: utf-8 -*-
"""
Pressed-steel cup reverse-engineered from the Revopoint scan  1009_01_mesh.ply     (v2)
==============================================================================

Run in FreeCAD:  Macro > Macros... > (select this file) > Execute

Model frame: revolve axis = global Z through the origin, flat top face at z = 0,
the cup hangs down to z = -59.3 and is open at the bottom.

Objects (group "Cup"):
    CupProfileSketch  ONE cubic B-spline (9 poles) = the whole wall from rim to the start of the flat top.
                      Edit it in the sketch (poles / knots) to reshape the wall.
    CupSide           Part::Revolution of that spline, 360 deg, Solid=False  (surface)
    TopPlateSketch    outer circle (end of the flat) + trilobal opening + 3 bolt holes
    TopPlate          planar face with the openings cut out
    LipWalls          stamped lip around the trilobal opening (LIP_DEPTH) and short collars in the bolt holes
    CupSurface        sewn shell of all of the above      -> SURFACE MODEL  (scanned outer skin)
    CupThickness      Part::Offset, Fill=True, Value = SHEET_T inward -> THICKNESS MODIFIER (~1 mm steel)

Measured from the scan:
    wall            B-spline fit to the profile, 0.115 mm rms (p95 0.23), rim r = 54.85, shoulder -> flat top at r = 42.5
    trilobal edge   3 lobes R16.37 + 3 blend arcs R17.51, rms 0.15 mm; notches point at the bolt holes
    lip             near-vertical wall around the trilobal opening, free edge 8.1 mm below the top face
    bolt holes      3 x D13.3 on R34.85; rolled edge + straight collar visible to ~3.2 mm (collar depth = lower bound)
    NOT measurable  the sheet thickness (scan = outer skin only) -> SHEET_T is set from your info (1 mm);
                    bend radii at the lip / collar tops (<~1 mm) are modelled as sharp
"""
import math
import FreeCAD as App
import Part
import Sketcher
from FreeCAD import Vector as V

# ----------------------------------------------------------------------------------------------
# PARAMETERS  (mm, degrees)
# ----------------------------------------------------------------------------------------------
SHEET_T     = 1.0        # sheet thickness of the thickness modifier
LIP_DEPTH   = 8.1        # depth of the stamped lip around the trilobal opening (scan: free edge at 8.1)
HOLE_COLLAR = 3.2        # depth of the straight collar in each bolt hole (0 = plain holes)

Z_BOT    = -59.3         # open rim z (top face is z = 0)
R_FLAT   = 42.5          # radius where the wall spline meets the flat top (tangent)

PHASE    = 54.9          # angle (deg, CCW from +X) of bolt hole #1 and of the first trilobal notch
BOLT_R   = 34.85
BOLT_D   = 13.3
N_HOLES  = 3

TRI_RHO0 = 21.451        # radius of the notch (tooth) tips
TRI_T    = 17.514        # blend ("tooth") arc radius
TRI_A    = 16.371        # lobe arc radius

# Wall spline: cubic B-spline, poles are (r, z).  Uniform-interior knot vector from the scan fit.
SPLINE_POLES = [(54.850, -59.300), (56.057, -44.586), (51.635, -27.302), (48.721, -8.404),
                (47.230,  -2.694), (45.261,  -1.008), (43.869,  -0.110), (43.642,  0.000),
                (R_FLAT,   0.000)]
SPLINE_KNOTS = [0.0, 0.65992, 0.8442, 0.91713, 0.94077, 0.95637, 1.0]
SPLINE_MULTS = [4, 1, 1, 1, 1, 1, 4]
SPLINE_DEG   = 3

# Optional: path to the PLY -> imports the scan aligned to this model for visual comparison
MESH_PATH = ""           # e.g. "/Users/lee/Downloads/1009_01_mesh.ply"

# ----------------------------------------------------------------------------------------------
# PURE GEOMETRY (no FreeCAD calls)
# ----------------------------------------------------------------------------------------------
def trilobal_geometry():
    """3 tooth arcs + 3 lobe arcs, tangent-continuous, CCW arcs in loop order."""
    s = TRI_RHO0 + TRI_T
    d = (s - math.sqrt(4 * (TRI_A + TRI_T) ** 2 - 3 * s * s)) / 2.0
    Tc = (s, 0.0)
    Lc = (d * 0.5, d * math.sqrt(3) / 2.0)
    u = (Lc[0] - Tc[0], Lc[1] - Tc[1])
    n = math.hypot(*u)
    u = (u[0] / n, u[1] / n)
    X = (Tc[0] + u[0] * TRI_T, Tc[1] + u[1] * TRI_T)
    a_tooth = math.atan2(X[1] - Tc[1], X[0] - Tc[0])
    a_lobe = math.atan2(X[1] - Lc[1], X[0] - Lc[0])
    arcs = []
    for kk in range(3):
        ph = math.radians(PHASE + 120.0 * kk)
        Tk = (s * math.cos(ph), s * math.sin(ph))
        Lk = (d * math.cos(ph + math.pi / 3), d * math.sin(ph + math.pi / 3))
        arcs.append(dict(kind="tooth", k=kk, c=Tk, r=TRI_T, a0=a_tooth + ph, a1=(2 * math.pi - a_tooth) + ph))
        arcs.append(dict(kind="lobe", k=kk, c=Lk, r=TRI_A, a0=a_lobe + ph, a1=(2 * math.pi / 3 - a_lobe) + ph))
    return arcs, d


def arc_end(arc, which):
    a = arc["a0"] if which == 0 else arc["a1"]
    return (arc["c"][0] + arc["r"] * math.cos(a), arc["c"][1] + arc["r"] * math.sin(a))


def hole_centres():
    return [(BOLT_R * math.cos(math.radians(PHASE + 360.0 * k / N_HOLES)),
             BOLT_R * math.sin(math.radians(PHASE + 360.0 * k / N_HOLES))) for k in range(N_HOLES)]


# ----------------------------------------------------------------------------------------------
# FREECAD BUILD
# ----------------------------------------------------------------------------------------------
def _warn(msg):
    App.Console.PrintWarning(msg + "\n")


def _info(msg):
    App.Console.PrintMessage(msg + "\n")


def build():
    doc = App.newDocument("Cup_ReverseEngineered")
    grp = doc.addObject("App::DocumentObjectGroup", "Cup")

    # ---------- 1. wall profile: ONE B-spline in the XZ plane (sketch x = radius, sketch y = global Z)
    prof = doc.addObject("Sketcher::SketchObject", "CupProfileSketch")
    prof.Placement = App.Placement(V(0, 0, 0), App.Rotation(V(1, 0, 0), 90))
    bs = Part.BSplineCurve()
    bs.buildFromPolesMultsKnots([V(r, z, 0) for (r, z) in SPLINE_POLES], SPLINE_MULTS, SPLINE_KNOTS,
                                False, SPLINE_DEG)
    prof.addGeometry(bs, False)
    try:
        prof.exposeInternalGeometry(0)       # show the control polygon so the poles can be dragged
    except Exception as e:
        _warn("exposeInternalGeometry skipped: %s" % e)
    doc.recompute()

    # ---------- 2. revolve it around the sketch's vertical axis (= global Z)
    side = None
    try:
        rev = doc.addObject("Part::Revolution", "CupSide")
        rev.Source = prof
        rev.AxisLink = (prof, ["V_Axis"])
        rev.Angle = 360.0
        rev.Solid = False
        doc.recompute()
        bb = rev.Shape.BoundBox
        if abs(bb.ZMin - Z_BOT) < 0.05 and abs(bb.ZMax) < 0.05 and 54.0 < bb.XMax < 56.5:
            side = rev
        else:
            _warn("Revolution axis looks wrong (%s) - using script revolve instead" % bb)
            doc.removeObject(rev.Name)
    except Exception as e:
        _warn("Part::Revolution failed (%s) - using script revolve instead" % e)
    if side is None:
        side = doc.addObject("Part::Feature", "CupSide")
        side.Shape = prof.Shape.revolve(V(0, 0, 0), V(0, 0, 1), 360)
        doc.recompute()
    grp.addObject(prof)
    grp.addObject(side)

    # ---------- 3. top plate: flat face r <= R_FLAT with trilobal opening and bolt holes
    top = doc.addObject("Sketcher::SketchObject", "TopPlateSketch")      # XY plane, z = 0
    top.addGeometry(Part.Circle(V(0, 0, 0), V(0, 0, 1), R_FLAT), False)
    arcs, d_lobe = trilobal_geometry()
    first = top.GeometryCount
    for a in arcs:
        top.addGeometry(Part.ArcOfCircle(Part.Circle(V(a["c"][0], a["c"][1], 0), V(0, 0, 1), a["r"]),
                                         a["a0"], a["a1"]), False)
    try:   # close the loop: tooth_k.start <-> lobe_k.start ; lobe_k.end <-> tooth_(k+1).end
        for kk in range(3):
            tooth, lobe, tooth_next = first + 2 * kk, first + 2 * kk + 1, first + 2 * ((kk + 1) % 3)
            top.addConstraint(Sketcher.Constraint("Coincident", tooth, 1, lobe, 1))
            top.addConstraint(Sketcher.Constraint("Coincident", lobe, 2, tooth_next, 2))
    except Exception as e:
        _warn("trilobal constraints skipped: %s" % e)
    for (hx, hy) in hole_centres():
        top.addGeometry(Part.Circle(V(hx, hy, 0), V(0, 0, 1), BOLT_D / 2.0), False)
    doc.recompute()

    plate = None
    try:
        plate = doc.addObject("Part::Face", "TopPlate")
        plate.Sources = [top]
        plate.FaceMakerClass = "Part::FaceMakerBullseye"
        doc.recompute()
        if plate.Shape.isNull() or len(plate.Shape.Faces) != 1:
            raise RuntimeError("Part::Face gave %d faces" % len(plate.Shape.Faces))
    except Exception as e:
        _warn("Part::Face failed (%s) - building plate by script" % e)
        if plate is not None:
            doc.removeObject(plate.Name)
        plate = doc.addObject("Part::Feature", "TopPlate")
        plate.Shape = Part.makeFace(top.Shape.Wires, "Part::FaceMakerBullseye")
        doc.recompute()
    grp.addObject(top)
    grp.addObject(plate)

    # ---------- 4. stamped lip around the trilobal opening + collars in the bolt holes
    walls = []
    pface = plate.Shape.Faces[0]
    inner = [w for w in pface.Wires if not w.isSame(pface.OuterWire)]
    inner.sort(key=lambda w: -w.Length)               # longest = trilobal, the rest = bolt holes
    for i, w in enumerate(inner):
        depth = LIP_DEPTH if i == 0 else HOLE_COLLAR
        if depth > 0:
            walls.extend(w.extrude(V(0, 0, -depth)).Faces)
    lips = doc.addObject("Part::Feature", "LipWalls")
    lips.Shape = Part.makeCompound(walls) if walls else Part.Shape()
    doc.recompute()
    grp.addObject(lips)

    # ---------- 5. SURFACE MODEL: sew everything into one shell
    faces = list(side.Shape.Faces) + list(plate.Shape.Faces) + walls
    comp = Part.makeCompound(faces)
    try:
        comp.sewShape(1e-3)
    except Exception:
        try:
            comp.sewShape()
        except Exception as e:
            _warn("sewShape unavailable: %s" % e)
    shells = list(comp.Shells)
    shell = max(shells, key=lambda s: s.Area) if shells else Part.Shell(faces)
    surf = doc.addObject("Part::Feature", "CupSurface")
    surf.Shape = shell
    doc.recompute()
    grp.addObject(surf)
    _info("CupSurface: %d faces in %d shell(s), area %.0f mm2, closed=%s valid=%s"
          % (len(shell.Faces), len(shells), shell.Area, shell.isClosed(), shell.isValid()))

    # ---------- 6. THICKNESS MODIFIER: Part::Offset with Fill (solid between skin and offset skin)
    skin = surf.Shape.BoundBox
    thick = None
    for join in ("Arc", "Intersection"):
        for sign in (-1.0, 1.0):
            if thick is not None:
                break
            off = None
            try:
                off = doc.addObject("Part::Offset", "CupThickness")
                off.Source = surf
                off.Value = sign * SHEET_T
                off.Mode = "Skin"
                off.Join = join
                off.Intersection = False
                off.SelfIntersection = False
                off.Fill = True
                doc.recompute()
                sh = off.Shape
                ok = (not sh.isNull()) and sh.isValid() and len(sh.Solids) >= 1 and sh.Volume > 0
                if ok:      # wall must grow inward from the scanned skin and be ~area*thickness thick
                    bb = sh.BoundBox
                    ok = (bb.XMax <= skin.XMax + 0.01 and bb.ZMax <= skin.ZMax + 0.01 and
                          abs(sh.Volume / (surf.Shape.Area * SHEET_T) - 1.0) < 0.25)
                if ok:
                    thick = off
                    _info("CupThickness ok: Join=%s Value=%+.2f volume=%.0f mm3" % (join, off.Value, sh.Volume))
                else:
                    doc.removeObject(off.Name)
            except Exception as e:
                _warn("offset attempt (join=%s sign=%+.0f) failed: %s" % (join, sign, e))
                try:
                    if off is not None:
                        doc.removeObject(off.Name)
                except Exception:
                    pass
    if thick is None:
        _warn("Could not build the thickened solid. CupSurface is fine - select it and use "
              "Part > Offset 3D object... (Fill offset on, try Join=Intersection, Value -1).")
    else:
        grp.addObject(thick)
        try:
            surf.ViewObject.Visibility = False
        except Exception:
            pass

    # ---------- 7. optional scan overlay
    if MESH_PATH:
        try:
            import Mesh
            before = set(o.Name for o in doc.Objects)
            Mesh.insert(MESH_PATH, doc.Name)
            M = _SCAN_TO_MODEL
            m = App.Matrix(M[0][0], M[0][1], M[0][2], M[0][3],
                           M[1][0], M[1][1], M[1][2], M[1][3],
                           M[2][0], M[2][1], M[2][2], M[2][3], 0, 0, 0, 1)
            for o in [o for o in doc.Objects if o.Name not in before]:
                o.Placement = App.Placement(m)
                grp.addObject(o)
            _info("scan mesh imported and aligned to the model frame")
        except Exception as e:
            _warn("mesh overlay failed: %s" % e)

    doc.recompute()
    try:
        import FreeCADGui
        FreeCADGui.SendMsgToActiveView("ViewFit")
        FreeCADGui.activeDocument().activeView().viewIsometric()
    except Exception:
        pass
    return doc


# scan frame -> model frame: local = M[:, :3] * p + M[:, 3]
_SCAN_TO_MODEL = [
    [0.999916879, 0.011495940, 0.005837666, -0.040734407],
    [0.000000000, 0.452770404, -0.891627142, 50.917578719],
    [-0.012893214, 0.891553030, 0.452732770, -58.025773198]
]

build()
